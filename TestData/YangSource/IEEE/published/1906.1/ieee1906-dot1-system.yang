module ieee1906-dot1-system
{
  yang-version 1.1;
  namespace "urn:ieee:std:1906.1:yang:ieee1906-dot1-system";
  prefix "system";

  import ieee1906-dot1-types { prefix types; }
  import ieee1906-dot1-metrics { prefix metrics; }
  import ieee1906-dot1-components { prefix components; }
  import ieee1906-dot1-definitions { prefix definitions; }
  import ieee1906-dot1-properties { prefix properties; }

  organization "IEEE 1906.1.1 - Recommended Practice for Nanoscale and
                Molecular Communication Framework Working Group";

  contact "Stephen F. Bush <bushsf@research.ge.com>
	   Guillaume Mantelet <gmantelet@voltigeurnetworks.com>";

  description  "This is the YANG model for the IEEE 1906.1-2015 - Recommended
                Practice for Nanoscale and Molecular Communication Framework.
                Clause 5 - Framework of a molecular and nanoscale communication
                network.";

  revision 2020-12-07
  {
    description "Initial version.";

	reference "[1] 'IEEE Recommended Practice for Nanoscale and Molecular
	                Communication Framework,' in IEEE Std 1906.1-2015, pp.1-64,
	                Jan. 11 2016 doi: 10.1109/IEEESTD.2016.7378262

			   [2] S. F. Bush, 'Active network architecture' in Nanoscale
			       Communication Networks, pp. 209-217, 2010, Artech House.

			   [3] S. F. Bush, J. L. Paluh, G. Piro, V. Rao, R. V. Prasad and
			       A. Eckford, 'Defining Communication at the Bottom,' in IEEE
			       Transactions on Molecular, Biological and Multi-Scale
			       Communications, vol. 1, no. 1, pp. 90-96, March 2015.
			       doi: 10.1109/TMBMC.2015.2465513

			   [4] K. Kyoda, Y. Tohsato, K. H. L. Ho and S. Onami, 'Biological
			       Dynamics Markup Language (BDML): an open format for
			       representing quantitative biological dynamics data,' in
			       Oxford University Press, Bioinformatics, pp. 1044-1052,
			       2015. doi: 10.1093/bioinformatics/btu767";
  }

  grouping system
  {
    description "This is an API for nanoscale systems. You can use it 
                 in your own modules and refine it.";

    leaf identifier
    {
      type types:urn;
      description "Identifying the system to make it a resource
                   available online.";
    }

    leaf title
    {
      type string;
      description "A short, optional title for this nanoscale system. 
                   Can be the name of the product.";
    }

    leaf-list organization
    {
      type string;
      description "The name of the vendor or the authority providing 
                   standards.";
    }

    leaf-list contact
    {
      type string;
      description "List of contact names. It is recommended to append 
                   the email address of the contact as well.";
    }

    leaf description
    {
      type string;
      description "An optional leaf describing what this nanoscale is 
                   expected to do.";
    }

    leaf version
    {
      type string;
      default "1.0";
      description "The version number of this document. No pattern
                   control for this leaf is defined. User may use
                   simple numbering or provide a date and time, or a
                   mix of them.";
    }

    leaf license
    {
      type string;
      description "The name of the license controlling rights to this
                   document";
    }

    leaf human-designed
    {
      type boolean;
      description "'Human-designed' means a system that occurs as a
                   result of conscious human intervention. For clarity,
                   human-designed systems may include naturally
                   occurring components in an arrangement or for a
                   purpose that is not otherwise naturally occurring.";
      default false;
    }

    leaf system-type
    {
      type identityref { base 'types:system-definition'; }
      description "Define the system type being described. Defaults to 
                   nanoscale-communication.

                   Communication is the act of conveying a message from
                   a transmitting party to a receiving party. This
                   includes the components of message, transmitter, 
                   receiver, medium, and message carriers. In nanoscale
                   communication at one to a few nanometers (nm), in 
                   the atomic range, local realism may be 
                   altered by quantum principles and include quantum 
                   entanglement.

                   Communication includes systems with many
                   transmitters and 
                   many receivers, for example broadcast (one to-all), 
                   multicast (many-to-one), and network (many-to-many) 
                   communication systems. The definition of a message
                   includes signals transmitted for control purposes. 
                   The definition of a nanoscale communication network
                   is illustrated in Figure 1 with a single-hop
                   network. The framework discussed in Clause 5 builds 
                   on this definition of communication.";
      default 'types:nanoscale-communication';
    }

    container definitions
    {
      uses definitions:definition;
      description "This container stores the list of definitions that
                   are part of the system.";
    }

    container components
    {
      uses components:component;
      description "This containers stores the list of components that
                   are part of the system.";
    }

    container properties
    {
      uses properties:property;
      description "This containers stores the list of optional
                   properties that provide extra definition of the
                   system.";
    }

    uses metrics:system-metrics;
  }

  container nanoscale-system
  {
    description "This is a nanoscale system. It can be used as is in
                 any of your XML or JSON files. It is also convenient
                 as debugging to represent the data tree.";
    uses system;
  }
}
