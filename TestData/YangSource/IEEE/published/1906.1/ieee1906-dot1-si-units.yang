module ieee1906-dot1-si-units
{
  yang-version 1.1;
  namespace "urn:ieee:std:1906.1:yang:ieee1906-dot1-si-units";
  prefix "ieee1906-dot1-si-units";

  import ietf-yang-metadata {  prefix md;  }
  import ieee1906-dot1-function {  prefix ieee1906-dot1-function;  }
  import ieee1906-dot1-math {  prefix ieee1906-dot1-math;  }

  organization "IEEE 1906.1.1 - Recommended Practice for Nanoscale and Molecular Communication
                Framework Working Group";

  contact  "Stephen F. Bush <bushsf@research.ge.com>
	    Guillaume Mantelet <gmantelet@voltigeurnetworks.com>";

  description "This YANG model aims to represent the fundamental SI units.

               Convention in this model is camelCase.

               YANG models are typically used to configure nodes on a telecommunication network.
               However, they can also be the support for exchanging data between simulators.
               Consequently, a scientific framework can be defined. The purpose of this model is
               to represent the fundamental layer for any scientific model by reusing scientific
               number notation, and by defining fundamental units.

               This YANG model implicitly recognizes SI prefixes. Note that the validation
               between the prefixes and the units should be performed by the NETCONF server, and
               this YANG model does not provide any clue to perform this validation. The SI
               prefixes are included in the following table. The factor number uses the format
               defined in the math YANG model:

               +------------------------------+---------+--------+---------------------+---------+
               | Factor |         Name        |  Symbol | Factor |         Name        |  Symbol |
               +------------------------------+---------+--------+---------------------+---------+
               |  10    |         deca        |   da    |  1e-1  |         deci        |    d    |
               |  1e2   |        hecto        |    h    |  1e-2  |        centi        |    c    |
               |  1e3   |         kilo        |    k    |  1e-3  |        milli        |    m    |
               |  1e6   |         mega        |    M    |  1e-4  |        micro        |    µ    |
               |  1e9   |         giga        |    G    |  1e-9  |         nano        |    n    |
               |  1e12  |         tera        |    T    |  1e-12 |         pico        |    p    |
               |  1e15  |         peta        |    P    |  1e-15 |        femto        |    f    |
               |  1e16  |          exa        |    E    |  1e-18 |         atto        |    a    |
               |  1e21  |        zetta        |    Z    |  1e-21 |        zepto        |    z    |
               |  1e24  |        yotta        |    Y    |  1e-24 |        yocto        |    y    |
               +------------------------------+---------+--------+---------------------+---------+

               This YANG model includes base and derived SI units with or without symbols. The
               following table provides the summary of covered units in alphabetical order:

               +---------------------------------------------------------------------------------+
               |                            SI BASE AND DERIVED UNITS                            |
               +---------------------------------+------+---------------------------------+------+
               | Name                            | Unit | Name                            | Unit |
               +---------------------------------+------+---------------------------------+------+
               | absorbed-dose                   |  Gy  | luminance                       |  Lv  |
               | absorbed-dose-rate              | Gy/s | luminous-flux                   |  lm  |
               | acceleration                    |   a  | luminous-intensity              |  cd  |
               | activity (radionuclide activit.)|  Bq  | magnetic-field-strength         |   H  |
               | amount-concentration (concentr.)|   c  | magnetic-flux                   |  Wb  |
               | amount-of-substance             | mol  | magnetic-flux-density           |   T  |
               | angular-acceleration            |rad/s2| mass                            |  kg  |
               | angular-velocity                | rad/s| mass-concentration              | ρ, γ |
               | area                            |   A  | mass-density                    |   ρ  |
               | capacitance                     |   F  | molar-energy                    | J/mol|
               | catalitic-activity              | katal| molar-heat-capacity (entropy)   | J/mol|
               | catalytic-activity-concentration|kat/m3| permeability                    |  H/m |
               | current-density                 |   j  | permittivity                    |  F/m |
               | dose-equivalent                 |  Sv  | plane-angle                     | rad  |
               | dynamic-viscosity               | Pa s | power (radiant-flux)            |   W  |
               | electric-charge                 |   C  | pressure                        |  Pa  |
               | electric-charge-density         | C/m3 | radiance                        |W/m2..|
               | electric-conductance            |   S  | radiant-intensity               | W/sr |
               | electric-current                |   A  | refractive-index                |      |
               | electric-field-strength         |  V/m | relative-permeability           |      |
               | electric-flux-density           | C/m2 | solid-angle                     |  sr  |
               | electric-potential-difference   |   V  | specific-energy                 | J/kg |
               | electric-resistance             |  Ohm | specific-heat-capacity(sp-entr.)|J/kg.K|
               | energy (work, amount-of-heat)   |   J  | specific-volume                 |   v  |
               | energy-density                  | J/m3 | surface-charge-density          | C/m2 |
               | exposure (x and Gamma rays)     | C/kg | surface-density                 |  ρA  |
               | force                           |   N  | surface-tension                 |  N/m |
               | frequency                       |  Hz  | temperature                     |  °C  |
               | heat-capacity (entropy)         |  J/K | thermal-conductivity            | W/m.K|
               | heat-flux-density (irradiance)  | W/m2 | thermodynamic-temperature       |   K  |
               | illuminance                     |  lx  | time  (duration)                |   s  |
               | inductance                      |   H  | velocity                        |   v  |
               | length                          |   m  | volume                          |   V  |
               |                                 |      | wavenumber                      |   σ  |
               +---------------------------------+------+---------------------------------+------+

               This YANG model also includes several common units that are not considered as SI
               units. They can be found appended to the fundamental units they derived from.
               Stokes only (kynematic-viscosity) does not have an SI counterpart and can be used
               as a type.

               Logarithm (neper, bel and decibel) can be used as implicit units as well. They are
               YANG identities in case they are needed. SI standard refers to committees defining
               several common constants, as the speed of light in vacuum, or the reduced Planck
               constant. They can be used as identities as well.

               +---------------------------------------------------------------------------------+
               |                            NON SI UNITS IN SI BROCHURE                          |
               +---------------------------------+------+---------------------------------+------+
               | Name                            | Unit | Name                            | Unit |
               +---------------------------------+------+---------------------------------+------+
               | acceleration-due-to-gravity     |  Gal | hartree-energy                  |  Eh  |
               | astronomical-unit               |  ua  | illuminance                     | phot |
               | atmospheric-pressure            |  bar | kynematic-viscosity **          |  St  |
               | atomic-unit-of-time             | ħ/Eh | luminance                       |  sb  |
               | bel-logarithm *                 |  bel | magnetic-field                  |  Oe  |
               | blood-pressure                  | mmHg | magnetic-flux-density           |   G  |
               | bohr-radius                     |  a0  | magnetic-flux                   |  Mx  |
               | crystal-length                  |   A  | nautical-mile                   |   M  |
               | decibel-logarithm *             |  dB  | nautical-speed                  |  kn  |
               | dynamic-viscosity               |   P  | neper-logarithm *               |  Nb  |
               | electron-mass                   |  me  | nuclear-cross-section           |   b  |
               | electronvolt                    |  eV  | quantum-of-time   ???????       |ħ/mec2|
               | elementary-charge               |   e  | reduced-planck-constant *       |   ħ  |
               | energy                          |  erg | speed-of-light (in vacuum) *    |   c  |
               | force                           |  dyn | unified-atomic-mass-unit        |  Da  |
               +---------------------------------+------+---------------------------------+------+

               *: Is an identity instead of being a derived unit.
               **: Can be used as a (Non SI) standalone type with stokes as unit.
               ";

  revision 2020-12-07
  {
    description "Initial version.";
	reference "The International System of Units: 8th Edition. 2006.
	           L. Lhotka, 'Defining and Using Metadata with YANG' RFC7952. 2016. pp1-21.";
  }

  extension units
  {
    argument name;
    description "To provide a unit to logical functions, such as groupings. A container can be
                 made of leafs, and have a unit on its own.";
  }

  extension derivedUnits
  {
    argument name;
    description "This extension allows the use of an SI (or even a non SI) unit for a specific
                 physic concept.

                 This helps a NETCONF server to accept different scales or magnitude orders for
                 the same meaning. For example, length can be expressed into 'astronomical-units'
                 or 'picometers'. As long as the NETCONF server can make the translation between
                 the units this should not raise an <rpc-error>. If a server fails to perform
                 this translation either:
                   1. Because it does not support the corresponding mapping
                   2. Because the unit provided is wrong (a client specifying a distance in kg)

                 The NETCONF node MUST return an <rpc-error> with a <bad-attribute> element
                 specifying that it could not perform the conversion.

                 YANG nodes allowing this extension should be leaf and list-leaf only. When using
                 this extension into the YANG leaf or list-leaf definition:
                   1. Use the unit names only, not the symbols.
                   2. Do not add the prefixes as they should be implicitly understood by the
                      NETCONF server.
                   3. Do not add neper, bel, and decibel unless you want to be explicit. For
                      example, a loss is unitless and unit should be 'one'. You do not have to
                      use this extension to accept 'dB' as it makes sense for a loss. However,
                      dBm must be defined in this extension to provide a ratio over 1mW.
                   3. Do not use this extension if the leaf has no unit substatement defined.

                 This extension should not be part of a container or a list for the reason there
                 can be inconsistency between the leaves and the container.

                 This extension helps the user only to use different SI and non SI units for the
                 same YANG type. This extension does not provide conversion between the units and
                 the NETCONF server should not rely on this extension to perform validations.

                 This extension should be used with an annotation, allowing the client to insert
                 an XML attribute specifying the unit attached to the value it provides. If the
                 attribute is not specified, then the fundamental unit expressed in the unit
                 substatement of the containing YANG leaf must be used.

                 When the client uses an XML attribute requesting a change of units, the client
                 should use names but may use symbols. The client should use SI prefix names but
                 may use SI prefix symbols instead (the charset for greek letters may not be
                 supported on the server).";
  }

  md:annotation unit
  {
    type string;
    description "This annotation defines the unit of the containing type if it is not the unit
                 specified in the units substatement of the corresponding type. For instance, an
                 astronomical distance can be expressed in 'ua' (astronomical units), or in 'Pm'
                 or even in petameter.

                 Pattern is not provided to this annotation because it is suggested to follow the
                 SI recommendation. Units:
                   1. should be SI or non SI unit name
                   2. may be SI or non SI symbol name
                   3. should have (if needed) SI prefix names (only if unit names are used)
                   4. might have SI prefix symbols (only if symbol name are used)
                   5. can be (if needed) np (neper logarithm), bel, or decibel, or dB.

                 Several examples lead to the same definition:
                 <transmitter nc:operation='create'>
                   <axial-length>1.2e-11</axial-length>
                 </transmitter>

                 <transmitter nc:operation='create'>
                   <axial-length sc:unit='nanometer'>12</axial-length>
                 </transmitter>

                 <transmitter nc:operation='create'>
                   <axial-length sc:unit='nm'>12</axial-length>
                 </transmitter>";
  }

  //=============================================================================================
  //
  //                                         SI PREFIXES
  //
  //=============================================================================================
  identity si-prefix
  {
    description "An SI prefix appended to a unit to denote a factor value to apply to the corresponding type.
                 NOTE: Do not use this identity directly. Instead, use this identity as a base for any SI prefix.";
  }

  identity deca
  {
    base "si-prefix";
    ieee1906-dot1-math:symbol "da";
    description "Factor 10";
  }

  identity hecto
  {
    base "si-prefix";
    ieee1906-dot1-math:symbol "h";
    description "Factor 1e2";
  }

  identity kilo
  {
    base "si-prefix";
    ieee1906-dot1-math:symbol "k";
    description "Factor 1e3";
  }

  identity mega
  {
    base "si-prefix";
    ieee1906-dot1-math:symbol "M";
    description "Factor 1e6";
  }

  identity giga
  {
    base "si-prefix";
    ieee1906-dot1-math:symbol "G";
    description "Factor 1e9";
  }

  identity tera
  {
    base "si-prefix";
    ieee1906-dot1-math:symbol "T";
    description "Factor 1e12";
  }

  identity peta
  {
    base "si-prefix";
    ieee1906-dot1-math:symbol "P";
    description "Factor 1e15";
  }

  identity exa
  {
    base "si-prefix";
    ieee1906-dot1-math:symbol "E";
    description "Factor 1e18";
  }

  identity zetta
  {
    base "si-prefix";
    ieee1906-dot1-math:symbol "Z";
    description "Factor 1e21";
  }

  identity yotta
  {
    base "si-prefix";
    ieee1906-dot1-math:symbol "Y";
    description "Factor 1e24";
  }

  identity deci
  {
    base "si-prefix";
    ieee1906-dot1-math:symbol "d";
    description "Factor 1e-1";
  }

  identity centi
  {
    base "si-prefix";
    ieee1906-dot1-math:symbol "c";
    description "Factor 1e-2";
  }

  identity milli
  {
    base "si-prefix";
    ieee1906-dot1-math:symbol "m";
    description "Factor 1e-3";
  }

  identity micro
  {
    base "si-prefix";
    ieee1906-dot1-math:symbol "µ";
    description "Factor 1e-6";
  }

  identity nano
  {
    base "si-prefix";
    ieee1906-dot1-math:symbol "n";
    description "Factor 1e-9";
  }

  identity pico
  {
    base "si-prefix";
    ieee1906-dot1-math:symbol "p";
    description "Factor 1e-12";
  }

  identity femto
  {
    base "si-prefix";
    ieee1906-dot1-math:symbol "f";
    description "Factor 1e-15";
  }

  identity atto
  {
    base "si-prefix";
    ieee1906-dot1-math:symbol "a";
    description "Factor 1e-18";
  }

  identity zepto
  {
    base "si-prefix";
    ieee1906-dot1-math:symbol "z";
    description "Factor 1e-21";
  }

  identity yocto
  {
    base "si-prefix";
    ieee1906-dot1-math:symbol "y";
    description "Factor 1e-24";
  }

  //=============================================================================================
  //
  //                                        SI DIMENSIONS
  //
  //=============================================================================================
  identity meter
  {
    ieee1906-dot1-math:symbol "m";
    description "Fundamental unit of distance.";
  }

  identity gram
  {
    ieee1906-dot1-math:symbol "g";
    description "Unit of mass.";
  }

  identity second
  {
    ieee1906-dot1-math:symbol "s";
    description "Fundamental unit of time.";
  }

  identity ampere
  {
    ieee1906-dot1-math:symbol "A";
    description "Fundamental unit of electric current.";
  }

  identity kelvin
  {
    ieee1906-dot1-math:symbol "K";
    description "Fundamental unit of thermodynamical temperature.";
  }

  identity mole
  {
    ieee1906-dot1-math:symbol "mol";
    description "Fundamental unit of amount of substance.";
  }

  identity candela
  {
    ieee1906-dot1-math:symbol "cd";
    description "Fundamental unit of luminous intensity.";
  }

  //=============================================================================================
  //
  //                                        SI BASE UNITS
  //
  //=============================================================================================
  typedef length
  {
	type ieee1906-dot1-function:variable;
	units meter;
	ieee1906-dot1-si-units:derivedUnits "astronomical-unit bohr-radius angstrom nautical-mile";
	description "The metre is the length of the path travelled by light in vacuum during a time
	             interval of 1/299 792 458 of a second.";
	reference "The International System of Units: 8th Edition 2006. Clause 2.1.1.1";
  }

  typedef mass
  {
	type ieee1906-dot1-function:variable;
	units kilogram;
	ieee1906-dot1-si-units:derivedUnits "tonne dalton electron-mass";
	description "The kilogram is the unit of mass; it is equal to the mass of the international
	             prototype of the kilogram.";
	reference "The International System of Units: 8th Edition 2006. Clause 2.1.1.2";
  }

  typedef time  // duration
  {
	type ieee1906-dot1-function:variable;
	units second;
	ieee1906-dot1-si-units:derivedUnits "day hour minute quantum-of-time atomic-unit-of-time"; //quantum-of-time????
	description "The second is the duration of 9 192 631 770 periods of the radiation
	             corresponding to the transition between the two hyperfine levels of the ground
	             state of the caesium 133 atom.";
	reference "The International System of Units: 8th Edition 2006. Clause 2.1.1.3";
  }

  typedef electric-current
  {
	type ieee1906-dot1-function:variable;
	units ampere;
	description "The ampere is that constant current which, if maintained in two straight
	             parallel conductors of infinite length, of negligible circular cross-section,
                 and placed 1 metre apart in vacuum, would produce between these conductors a
                 force equal to 2 × 10−7 newton per metre of length.";
	reference "The International System of Units: 8th Edition 2006. Clause 2.1.1.4";
  }

  typedef thermodynamic-temperature
  {
	type ieee1906-dot1-function:variable;
	units kelvin;
	description "The kelvin, unit of thermodynamic temperature, is the fraction 1/273.16 of the
                 thermodynamic temperature of the triple point of water.";
	reference "The International System of Units: 8th Edition 2006. Clause 2.1.1.5";
  }

  typedef amount-of-substance
  {
	type ieee1906-dot1-function:variable;
	units mole;
	description "1. The mole is the amount of substance of a system which contains as many
	                elementary entities as there are atoms in 0.012 kilogram of carbon 12; its
	                symbol is 'mol.'

                 2. When the mole is used, the elementary entities must be specified and may be
                    atoms, molecules, ions, electrons, other particles, or specified groups of
                    such particles.";
	reference "The International System of Units: 8th Edition 2006. Clause 2.1.1.6";
  }

  typedef luminous-intensity
  {
	type ieee1906-dot1-function:variable;
	units candela;
	description "The candela is the luminous intensity, in a given direction, of a source that
                 emits monochromatic radiation of frequency 540 × 1012 hertz and that has a
                 radiant intensity in that direction of 1/683 watt per steradian. ";
	reference "The International System of Units: 8th Edition 2006. Clause 2.1.1.7";
  }

  //=============================================================================================
  //
  //                            SI DERIVED UNITS WITHOUT SPECIAL NAMES
  //
  //=============================================================================================
  identity si-derived-unit
  {
    description "Logical placeholder. You should not use this.";
  }

  typedef area
  {
	type ieee1906-dot1-function:variable;
	units meter^2;
	ieee1906-dot1-si-units:derivedUnits "hectare barn";
	description "A measure of the total area occupied by the surface of a physical body";
	reference "The International System of Units: 8th Edition 2006. Clause 2.2.1";
  }

  identity area
  {
    base si-derived-unit;
    description "See corresponding typedef";
  }

  typedef volume
  {
	type ieee1906-dot1-function:variable;
	units meter^3;
	ieee1906-dot1-si-units:derivedUnits "litre";
	description "A measure of the total volume within the surface of a physical body";
	reference "The International System of Units: 8th Edition 2006. Clause 2.2.1";
  }

  identity volume
  {
    base si-derived-unit;
    description "See corresponding typedef";
  }

  typedef velocity   // speed
  {
	type ieee1906-dot1-function:variable;
	units meter/second;
	ieee1906-dot1-si-units:derivedUnits knot;
	description "A measure of the length of the path travelled by a physical body during a time
	             interval of 1 second.";
	reference "The International System of Units: 8th Edition 2006. Clause 2.2.1";
  }

  identity velocity
  {
    base si-derived-unit;
    description "See corresponding typedef";
  }

  typedef acceleration
  {
	type ieee1906-dot1-function:variable;
	units meter/second^2;
	ieee1906-dot1-si-units:derivedUnits gal;
	description "A measure of the change in velocity of a physical body during a time interval of
	             1 second.";
	reference "The International System of Units: 8th Edition 2006. Clause 2.2.1";
  }

  identity acceleration
  {
    base si-derived-unit;
    description "See corresponding typedef";
  }

  typedef wavenumber
  {
	type ieee1906-dot1-function:variable;
	units meter-1;
	description "Derived unit expressed in terms of base units: m^−1.";
	reference "The International System of Units: 8th Edition 2006. Clause 2.2.1";
  }

  identity wavenumber
  {
    base si-derived-unit;
    description "See corresponding typedef";
  }

  typedef mass-density //density
  {
	type ieee1906-dot1-function:variable;
	units kilogram/meter3;
	description "Derived unit expressed in terms of base units: kg m^3.";
	reference "The International System of Units: 8th Edition 2006. Clause 2.2.1";
  }

  identity mass-density
  {
    base si-derived-unit;
    description "See corresponding typedef";
  }

  typedef surface-density
  {
	type ieee1906-dot1-function:variable;
	units kilogram/meter2;
	description "Derived unit expressed in terms of base units: kg m^-2.";
	reference "The International System of Units: 8th Edition 2006. Clause 2.2.1";
  }

  identity surface-density
  {
    base si-derived-unit;
    description "See corresponding typedef";
  }

  typedef specific-volume
  {
	type ieee1906-dot1-function:variable;
	units meter3/kilogram;
	description "Derived unit expressed in terms of base units: m^3 kg^-1";
	reference "The International System of Units: 8th Edition 2006. Clause 2.2.1";
  }

  identity specific-volume
  {
    base si-derived-unit;
    description "See corresponding typedef";
  }

  typedef current-density
  {
	type ieee1906-dot1-function:variable;
	units ampere/meter2;
	description "Derived unit expressed in terms of base units: A m^-2";
	reference "The International System of Units: 8th Edition 2006. Clause 2.2.1";
  }

  identity current-density
  {
	base si-derived-unit;
    description "See corresponding typedef";
  }

  typedef magnetic-field-strength
  {
	type ieee1906-dot1-function:variable;
	units ampere/meter;
	ieee1906-dot1-si-units:derivedUnits oersted;
	description "Derived unit expressed in terms of base units: A m^-1";
	reference "The International System of Units: 8th Edition 2006. Clause 2.2.1";
  }

  identity magnetic-field-strength
  {
    base si-derived-unit;
    description "See corresponding typedef";
  }

  typedef amount-concentration // concentration
  {
	type ieee1906-dot1-function:variable;
	units mole/meter3;
	description "Derived unit expressed in terms of base units: mol m^-3";
	reference "The International System of Units: 8th Edition 2006. Clause 2.2.1";
  }

  identity amount-concentration
  {
    base si-derived-unit;
    description "See corresponding typedef";
  }

  typedef mass-concentration
  {
	type ieee1906-dot1-function:variable;
	units kilogram/meter3;
	description "Derived unit expressed in terms of base units: kg m^-3";
 	reference "The International System of Units: 8th Edition 2006. Clause 2.2.1";
  }

  identity mass-concentration
  {
    base si-derived-unit;
    description "See corresponding typedef";
  }

  typedef luminance
  {
	type ieee1906-dot1-function:variable;
	units candela/meter2;
	ieee1906-dot1-si-units:derivedUnits stilb;
	description "Derived unit expressed in terms of base units: cd m^-2";
	reference "The International System of Units: 8th Edition 2006. Clause 2.2.1";
  }

  identity luminance
  {
    base si-derived-unit;
    description "See corresponding typedef";
  }

  typedef refractive-index
  {
	type ieee1906-dot1-function:variable;
	units one;
	description "Derived unit expressed in terms of base units: 1. [v]alues of quantities with unit one, are expressed simply as numbers.";
	reference "The International System of Units: 8th Edition 2006. Clause 2.2.1";
  }

  identity refractive-index
  {
    base si-derived-unit;
    description "See corresponding typedef";
  }

  typedef relative-permeability
  {
	type ieee1906-dot1-function:variable;
	units one;
	description "Derived unit expressed in terms of base units: 1. [v]alues of quantities with unit one, are expressed simply as numbers.";
	reference "The International System of Units: 8th Edition 2006. Clause 2.2.1";
  }

  identity relative-permeability
  {
    base si-derived-unit;
    description "See corresponding typedef";
  }

  //=============================================================================================
  //
  //                       SI DERIVED UNITS WITH SPECIAL NAMES AND SYMBOLS
  //
  //=============================================================================================
  typedef plane-angle
  {
    type ieee1906-dot1-function:variable;
	units one;
	ieee1906-dot1-si-units:derivedUnits "radian degree minute second";
	description "Derived unit expressed in terms of base units: 1. [v]alues of quantities with unit one, are expressed simply as numbers. [P]lane angle, radian, rad = m/m.";
	reference "The International System of Units: 8th Edition 2006. Clause 2.2.2";
  }

  identity plane-angle
  {
    base si-derived-unit;
    description "See corresponding typedef";
  }

  typedef solid-angle
  {
    type ieee1906-dot1-function:variable;
    units one;
	ieee1906-dot1-si-units:derivedUnits steradian;
	description "Derived unit expressed in terms of base units: 1. [V]alues of quantities with unit one, are expressed simply as
numbers. [S]olid angle, steradian, sr = m^2/m^2.";
	reference "The International System of Units: 8th Edition 2006. Clause 2.2.2";
  }

  identity solid-angle
  {
    base si-derived-unit;
    description "See corresponding typedef";
  }

  typedef frequency
  {
	type ieee1906-dot1-function:variable;
	units second^-1;
	ieee1906-dot1-si-units:derivedUnits hertz;
	description "Derived unit expressed in terms of base units: s^-1. [F]requency, hertz, Hz = s^−1.";
	reference "The International System of Units: 8th Edition 2006. Clause 2.2.2";
  }

  identity frequency
  {
    base si-derived-unit;
    description "See corresponding typedef";
  }

  typedef force
  {
  	type ieee1906-dot1-function:variable;
	units kilogram.meter/second^2;
	ieee1906-dot1-si-units:derivedUnits "newton dyne";
	description "Derived unit expressed in terms of base units: kg m s^-2. [F]orce, newton, N = kg m s−2.";
	reference "The International System of Units: 8th Edition 2006. Clause 2.2.2";
  }

  identity force
  {
    base si-derived-unit;
    description "See corresponding typedef";
  }

  typedef pressure // stress
  {
  	type ieee1906-dot1-function:variable;
	units kilogram/meter.second^2;
	ieee1906-dot1-si-units:derivedUnits "pascal bar mmHg";
	description "Derived unit expressed in terms of base units: kg m^-1 s^2. [P]ressure, stress, pascal, Pa = kg m−1 s−2.";
	reference "The International System of Units: 8th Edition 2006. Clause 2.2.2";
  }

  identity pressure
  {
    base si-derived-unit;
    description "See corresponding typedef";
  }

  typedef energy //work, amount-of-heat
  {
    type ieee1906-dot1-function:variable;
    units kilogram.meter^2/second^2;
	ieee1906-dot1-si-units:derivedUnits "joule electronvolt hartree-energy erg";
	description "Derived unit expressed in terms of base units: kg m^2 s^-2. [E]nergy, work, joule, J = kg m^2 s^−2 N m.";
	reference "The International System of Units: 8th Edition 2006. Clause 2.2.2";
  }

  identity energy
  {
    base si-derived-unit;
    description "See corresponding typedef";
  }

  typedef power //radiant-flux
  {
    type ieee1906-dot1-function:variable;
    units kilogram.meter^2/second^3;
	ieee1906-dot1-si-units:derivedUnits watt;
	description "Derived unit expressed in terms of base units: kg m^2 s^-3. [P]ower, radiant flux, watt, W = kg m^2 s^−3 J/s.";
	reference "The International System of Units: 8th Edition 2006. Clause 2.2.2";
  }

  identity power
  {
    base si-derived-unit;
    description "See corresponding typedef";
  }

  typedef electric-charge  //amountOfElectricity
  {
	type ieee1906-dot1-function:variable;
	units ampere.second;
	ieee1906-dot1-si-units:derivedUnits "coulomb elementary-charge";
	description "Derived unit expressed in terms of base units: A s.
                [C]harge, coulomb, C = A s.";
	reference "The International System of Units: 8th Edition 2006. Clause 2.2.2";
  }

  identity electric-charge
  {
    base si-derived-unit;
    description "See corresponding typedef";
  }

  typedef electric-potential-difference //electromotiveForce
  {
    type ieee1906-dot1-function:variable;
    units kilogram.meter^2/second^3.ampere;
	ieee1906-dot1-si-units:derivedUnits volt;
	description "Derived unit expressed in terms of base units: kg m^2 s^-3 A^-1. [E]lectric potential difference, volt, V = kg m^2 s^−3 A^−1, W/A.";
	reference "The International System of Units: 8th Edition 2006. Clause 2.2.2";
  }

  identity electric-potential-difference
  {
    base si-derived-unit;
    description "See corresponding typedef";
  }

  typedef capacitance
  {
	type ieee1906-dot1-function:variable;
	units ampere^2.second^4/kilogram.meter^2;
	ieee1906-dot1-si-units:derivedUnits farad;
	description "Derived unit expressed in terms of base units: A^2 s^4 kg^-1 m^-2. [C]apacitance, farad, F = kg^−1 m^−2 s^4 A^2, C/V.";
	reference "The International System of Units: 8th Edition 2006. Clause 2.2.2";
  }

  identity capacitance
  {
    base si-derived-unit;
    description "See corresponding typedef";
  }

  typedef electric-resistance
  {
	type ieee1906-dot1-function:variable;
	units kilogram.meter^2/second^3.ampere^2;
	ieee1906-dot1-si-units:derivedUnits ohm;
	description "Derived unit expressed in terms of base units: kg m^2 s^-3 A^-2. [E]lectric resistance, ohm, Ω = kg m^2 s^−3 A^−2, V/A.";
	reference "The International System of Units: 8th Edition 2006. Clause 2.2.2";
  }

  identity electric-resistance
  {
    base si-derived-unit;
    description "See corresponding typedef";
  }

  typedef electric-conductance
  {
	type ieee1906-dot1-function:variable;
	units second^3.ampere^2/kilogram.meter^2;
	ieee1906-dot1-si-units:derivedUnits siemens;
	description "Derived unit expressed in terms of base units: s^3 A^2 kg^-1 m^-2. [E]lectric conductance, siemens, S = kg^−1 m^−2 s^3 A^2, A/V.";
	reference "The International System of Units: 8th Edition 2006. Clause 2.2.2";
  }

  identity electric-conductance
  {
    base si-derived-unit;
    description "See corresponding typedef";
  }

  typedef magnetic-flux
  {
    type ieee1906-dot1-function:variable;
    units kilogram.meter^2/second^2.ampere;
	ieee1906-dot1-si-units:derivedUnits "weber maxwell";
	description "Derived unit expressed in terms of base units: kg m^2 s^-2 A^-1. [M]agnetic flux, weber, Wb = kg m^2 s^−2 A^−1, V s.";
	reference "The International System of Units: 8th Edition 2006. Clause 2.2.2";
  }

  identity magnetic-flux
  {
    base si-derived-unit;
    description "See corresponding typedef";
  }

  typedef magnetic-flux-density
  {
    type ieee1906-dot1-function:variable;
    units kilogram/second^2.ampere;
	ieee1906-dot1-si-units:derivedUnits "tesla gauss";
	description "[M]agnetic flux density, tesla, T = kg s^−2 A^−1, Wb/m^2.";
	reference "The International System of Units: 8th Edition 2006. Clause 2.2.2";
  }

  identity magnetic-flux-density
  {
    base si-derived-unit;
    description "See corresponding typedef";
  }

  typedef inductance
  {
    type ieee1906-dot1-function:variable;
    units kilogram.meter^2/second^2.ampere^2;
	ieee1906-dot1-si-units:derivedUnits henry;
	description "[I]nductance, henry, H = kg m^2 s^−2 A^−2, Wb/A.";
	reference "The International System of Units: 8th Edition 2006. Clause 2.2.2";
  }

  identity inductance
  {
    base si-derived-unit;
    description "See corresponding typedef";
  }

  typedef temperature
  {
	type ieee1906-dot1-function:variable;
	units kelvin;
	ieee1906-dot1-si-units:derivedUnits "celsius fahrenheit";
	description "Celsius temperature, degree Celsius, deg C = K.";
	reference "The International System of Units: 8th Edition 2006. Clause 2.2.2";
  }

  identity temperature
  {
    base si-derived-unit;
    description "See corresponding typedef";
  }

  typedef luminous-flux
  {
	type ieee1906-dot1-function:variable;
	units candela.steradian;
	ieee1906-dot1-si-units:derivedUnits lumen;
	description "[L]uminous flux, lumen, lm = cd sr, cd sr.";
	reference "The International System of Units: 8th Edition 2006. Clause 2.2.2";
  }

  identity luminous-flux
  {
    base si-derived-unit;
    description "See corresponding typedef";
  }

  typedef illuminance
  {
	type ieee1906-dot1-function:variable;
	units candela.steradian/meter^2;
	ieee1906-dot1-si-units:derivedUnits "lux phot";
	description "[I]lluminance, lux, lx = cd sr m^−2, lm/m^2.";
	reference "The International System of Units: 8th Edition 2006. Clause 2.2.2";
  }

  identity illuminance
  {
    base si-derived-unit;
    description "See corresponding typedef";
  }

  typedef activity //(referred to a radionuclide)
  {
	type ieee1906-dot1-function:variable;
	units second^-1;
	ieee1906-dot1-si-units:derivedUnits becquerel;
	description "[A]ctivity referred to a radionuclide, becquerel, Bq = s^−1.";
	reference "The International System of Units: 8th Edition 2006. Clause 2.2.2";
  }

  identity activity
  {
    base si-derived-unit;
    description "See corresponding typedef";
  }

  typedef absorbed-dose //specific dose, kerma
  {
    type ieee1906-dot1-function:variable;
    units meter^2/second^2;
	ieee1906-dot1-si-units:derivedUnits gray;
	description "[A]bsorbed dose, kerma, gray, Gy = m^2 s^−2, J/kg.";
	reference "The International System of Units: 8th Edition 2006. Clause 2.2.2";
  }

  identity absorbed-dose
  {
    base si-derived-unit;
    description "See corresponding typedef";
  }

  typedef dose-equivalent
  {
    type ieee1906-dot1-function:variable;
    units meter^2/second^2;  // Sievert (J/kg)
	ieee1906-dot1-si-units:derivedUnits sievert;
	description "[D]ose equivalent, sievert, Sv = m^2 s^−2, J/kg.";
	reference "The International System of Units: 8th Edition 2006. Clause 2.2.2";
  }

  identity dose-equivalent
  {
    base si-derived-unit;
    description "See corresponding typedef";
  }

  typedef catalytic-activity
  {
	type ieee1906-dot1-function:variable;
	units mole/second;
	ieee1906-dot1-si-units:derivedUnits katal;
	description "[C]atalytic activity, katal, kat = mol s^−1.";
	reference "The International System of Units: 8th Edition 2006. Clause 2.2.2";
  }

  identity catalytic-activity
  {
    base si-derived-unit;
    description "See corresponding typedef";
  }

  typedef dynamic-viscosity
  {
	type ieee1906-dot1-function:variable;
	units kilogram/second;
	ieee1906-dot1-si-units:derivedUnits "pascal.second poise";
	description "[D]ynamic viscosity, pascal second, Pa s, kg m^−1 s^−1.";
	reference "The International System of Units: 8th Edition 2006. Clause 2.2.2";
  }

  identity dynamic-viscosity
  {
    base si-derived-unit;
    description "See corresponding typedef";
  }

  typedef moment-of-force
  {
	type ieee1906-dot1-function:variable;
	units meter^2.kilogram/second^2; //N.m
	ieee1906-dot1-si-units:derivedUnits "newton.meter";
	description "[M]oment of force, newton meter, N m, kg m^2 s^−2.";
	reference "The International System of Units: 8th Edition 2006. Clause 2.2.2";
  }

  identity moment-of-force
  {
    base si-derived-unit;
    description "See corresponding typedef";
  }

  typedef surface-tension
  {
	type ieee1906-dot1-function:variable;
	units kilogram/second^2;
	ieee1906-dot1-si-units:derivedUnits "newton/meter";
	description "[S]urface tension, newton per meter, N m^−1, kg s^−2.";
	reference "The International System of Units: 8th Edition 2006. Clause 2.2.2";
  }

  identity surface-tension
  {
    base si-derived-unit;
    description "See corresponding typedef";
  }

  typedef angular-velocity
  {
	type ieee1906-dot1-function:variable;
	units s^-1;
	ieee1906-dot1-si-units:derivedUnits "radian/second";
	description "[A]ngular velocity, angular frequency, radian per second, rad s^−1, s^−1.";
	reference "The International System of Units: 8th Edition 2006. Clause 2.2.2";
  }

  identity angular-velocity
  {
    base si-derived-unit;
    description "See corresponding typedef";
  }

  typedef angular-acceleration
  {
	type ieee1906-dot1-function:variable;
	units s^-2;
	ieee1906-dot1-si-units:derivedUnits "radian/second^2";
	description "[A]ngular acceleration, radian per second squared, rad/s^2, s−2.";
	reference "The International System of Units: 8th Edition 2006. Clause 2.2.2";
  }

  identity angular-acceleration
  {
    base si-derived-unit;
    description "See corresponding typedef";
  }

  typedef heat-flux-density // irradiance
  {
	type ieee1906-dot1-function:variable;
	units kilogram/s^3;
	ieee1906-dot1-si-units:derivedUnits "watt/meter^2";
	description "[H]eat flux density, irradiance, watt per square meter, W/m^2, kg s^−3.";
	reference "The International System of Units: 8th Edition 2006. Clause 2.2.2";
  }

  identity heat-flux-density
  {
    base si-derived-unit;
    description "See corresponding typedef";
  }

  typedef heat-capacity     // entropy
  {
	type ieee1906-dot1-function:variable;
	units meter^2.kilogram/second^2.K;
	ieee1906-dot1-si-units:derivedUnits "joule/kelvin";
	description "[H]eat capacity, entropy, joule per kelvin, J K^−1, kg m^2 s^−2 K^−1.";
	reference "The International System of Units: 8th Edition 2006. Clause 2.2.2";
  }

  identity heat-capacity
  {
    base si-derived-unit;
    description "See corresponding typedef";
  }

  typedef specific-heat-capacity     // specific-entropy
  {
	type ieee1906-dot1-function:variable;
	units meter^2/second^2.K;
	ieee1906-dot1-si-units:derivedUnits "joule/kilogram.kelvin";
	description "[S]pecific heat capacity, specific entropy, joule per kilogram kelvin, J K^−1 kg^−1, m^2 s^−2 K^−1.";
	reference "The International System of Units: 8th Edition 2006. Clause 2.2.2";
  }

  identity specific-heat-capacity
  {
    base si-derived-unit;
    description "See corresponding typedef";
  }

  typedef specific-energy
  {
	type ieee1906-dot1-function:variable;
	units meter^2/second^2;
	ieee1906-dot1-si-units:derivedUnits "joule/kilogram";
	description "[S]pecific energy, joule per kilogram, J kg^−1, m^2 s^−2.";
	reference "The International System of Units: 8th Edition 2006. Clause 2.2.2";
  }

  identity specific-energy
  {
    base si-derived-unit;
    description "See corresponding typedef";
  }

  typedef thermal-conductivity
  {
	type ieee1906-dot1-function:variable;
	units meter.kilogram/second^3.K;
	ieee1906-dot1-si-units:derivedUnits "watt/meter.kelvin";
	description "[T]hermal conductivity, watt per meter kelvin, W m^−1 K^−1, kg m s^−3 K^−1.";
	reference "The International System of Units: 8th Edition 2006. Clause 2.2.2";
  }

  identity thermal-conductivity
  {
    base si-derived-unit;
    description "See corresponding typedef";
  }

  typedef energy-density
  {
	type ieee1906-dot1-function:variable;
	units kilogram/meter.second^2;
	ieee1906-dot1-si-units:derivedUnits "joule/meter^3";
	description "[E]nergy density, joule per cubic meter, J m^−3, kg m^−1 s^−2.";
	reference "The International System of Units: 8th Edition 2006. Clause 2.2.2";
  }

  identity energy-density
  {
    base si-derived-unit;
    description "See corresponding typedef";
  }

  typedef electric-field-strength
  {
	type ieee1906-dot1-function:variable;
	units meter.kilogram/second^3.ampere;
	ieee1906-dot1-si-units:derivedUnits "volt/meter";
	description "[E]lectric field strength, volt per meter, V m^−1, kg m s^−3 A^−1.";
	reference "The International System of Units: 8th Edition 2006. Clause 2.2.2";
  }

  identity electric-field-strength
  {
    base si-derived-unit;
    description "See corresponding typedef";
  }

  typedef electric-charge-density
  {
	type ieee1906-dot1-function:variable;
	units second.ampere/meter^3;
	ieee1906-dot1-si-units:derivedUnits coulomb/meter^3;
	description "[E]lectric charge density, coulomb per cubic meter, C m^−3 A s m^−3.";
	reference "The International System of Units: 8th Edition 2006. Clause 2.2.2";
  }

  identity electric-charge-density
  {
    base si-derived-unit;
    description "See corresponding typedef";
  }

  typedef surface-charge-density
  {
	type ieee1906-dot1-function:variable;
	units second.ampere/meter^2;
	ieee1906-dot1-si-units:derivedUnits coulomb/meter^2;
	description "[S]urface charge density, coulomb per square meter, C m^−2, A s m^−2.";
	reference "The International System of Units: 8th Edition 2006. Clause 2.2.2";
  }

  identity surface-charge-density
  {
    base si-derived-unit;
    description "See corresponding typedef";
  }

  typedef electric-flux-density  //electricDisplacement
  {
	type ieee1906-dot1-function:variable;
	units second.ampere/meter^2;
	ieee1906-dot1-si-units:derivedUnits coulomb/meter^2;
	description "[E]lectric flux density, electric displacement, coulomb per square meter, C m^−2, A s m^−2.";
	reference "The International System of Units: 8th Edition 2006. Clause 2.2.2";
  }

  identity electric-flux-density
  {
    base si-derived-unit;
    description "See corresponding typedef";
  }

  typedef permittivity
  {
	type ieee1906-dot1-function:variable;
	units second^4.ampere^2/meter^3.kilogram;
	ieee1906-dot1-si-units:derivedUnits farad/meter;
	description "[P]ermittivity, farad per meter, F m^−1, kg^−1 m^−3 s^4 A^2.";
	reference "The International System of Units: 8th Edition 2006. Clause 2.2.2";
  }

  identity permittivity
  {
    base si-derived-unit;
    description "See corresponding typedef";
  }

  typedef permeability
  {
	type ieee1906-dot1-function:variable;
	units meter.kilogram/second^2.ampere^2;
	ieee1906-dot1-si-units:derivedUnits henry/meter;
	description "[P]ermeability, henry per meter, H m^−1, kg m s^−2 A^−2.";
	reference "The International System of Units: 8th Edition 2006. Clause 2.2.2";
  }

  identity permeability
  {
    base si-derived-unit;
    description "See corresponding typedef";
  }

  typedef molar-energy
  {
	type ieee1906-dot1-function:variable;
	units meter^2.kilogram/second^2.mole;
	ieee1906-dot1-si-units:derivedUnits joule/mole;
	description "[M]olar energy, joule per mole. J mol^−1, kg m^2 s^−2 mol^−1.";
	reference "The International System of Units: 8th Edition 2006. Clause 2.2.2";
  }

  identity molar-energy
  {
    base si-derived-unit;
    description "See corresponding typedef";
  }

  typedef molar-heat-capacity  //molarEntropy
  {
	type ieee1906-dot1-function:variable;
	units meter^2.kilogram/second^2.mole.kelvin;
	ieee1906-dot1-si-units:derivedUnits joule/mole.kelvin;
	description "[M]olar entropy, molar heat capacity, joule per mole kelvin, J K−1 mol−1, kg m^2 s^−2 mol^−1 K^−1.";
	reference "The International System of Units: 8th Edition 2006. Clause 2.2.2";
  }

  identity molar-heat-capacity
  {
    base si-derived-unit;
    description "See corresponding typedef";
  }

  typedef exposure //(x and gamma rays)
  {
	type ieee1906-dot1-function:variable;
	units second.ampere/kilogram;
	ieee1906-dot1-si-units:derivedUnits coulomb/kilogram;
	description "[E]xposure (x- and γ-rays), coulomb per kilogram, C kg^−1, A s kg^−1.";
	reference "The International System of Units: 8th Edition 2006. Clause 2.2.2";
  }

  identity exposure
  {
    base si-derived-unit;
    description "See corresponding typedef";
  }

  typedef absorbed-dose-rate
  {
	type ieee1906-dot1-function:variable;
	units meter^2/second^3;
	ieee1906-dot1-si-units:derivedUnits gray/second;
	description "[A]bsorbed dose rate, gray per second, Gy s^−1, m^2 s^−3.";
	reference "The International System of Units: 8th Edition 2006. Clause 2.2.2";
  }

  identity absorbed-dose-rate
  {
    base si-derived-unit;
    description "See corresponding typedef";
  }

  typedef radiant-intensity
  {
	type ieee1906-dot1-function:variable;
	units meter^2.kilogram/second^3;
	ieee1906-dot1-si-units:derivedUnits watt/steradian;
	description "[R]adiant intensity, watt per steradian, W sr^−1, kg m^2 s^−3.";
	reference "The International System of Units: 8th Edition 2006. Clause 2.2.2";
  }

  identity radiant-intensity
  {
    base si-derived-unit;
    description "See corresponding typedef";
  }

  typedef radiance
  {
	type ieee1906-dot1-function:variable;
	units kilogram/second^3;
	ieee1906-dot1-si-units:derivedUnits watt/meter^2.steradian;
	description "[R]adiance, watt per square meter, steradian W sr^−1 m^−2, kg s^−3.";
	reference "The International System of Units: 8th Edition 2006. Clause 2.2.2";
  }

  identity radiance
  {
    base si-derived-unit;
    description "See corresponding typedef";
  }

  typedef catalytic-activity-concentration
  {
	type ieee1906-dot1-function:variable;
	units mol/second^3.second;
	ieee1906-dot1-si-units:derivedUnits katal/meter^3;
	description "[C]atalytic activity concentration, katal per cubic meter, kat m^−3, mol s^−1 m^−3.";
	reference "The International System of Units: 8th Edition 2006. Clause 2.2.2";
  }

  identity catalytic-activity-concentration
  {
    base si-derived-unit;
    description "See corresponding typedef";
  }

  //=============================================================================================
  //
  //            NON-SI UNITS WHOSE VALUES IN SI UNITS MUST BE OBTAINED EXPERIMENTALLY
  //
  //=============================================================================================
  identity speed-of-light
  {
    description "The speed of light in vacuum which is equal to 299 792 458 m/s (exact)";
    reference "The International System of Units: 8th Edition 2006. Clause 4.1";
  }

  identity reduced-planck-constant
  {
	description "It equals 1.054 571 68 (18) × 10−34 J s";
	reference "The International System of Units: 8th Edition 2006. Clause 4.1
	           P.J. Mohr and B.N. Taylor, Rev. Mod. Phys., 2005, 77, 1-107";
  }

  identity electron-mass
  {
	description "It equals 9.109 3826 (16) × 10−31 kg ";
	reference "The International System of Units: 8th Edition 2006. Clause 4.1
	           P.J. Mohr and B.N. Taylor, Rev. Mod. Phys., 2005, 77, 1-107";
  }

  identity quantum-of-time  // ????
  {
	description "It equals 1.288 088 6677 (86) × 10−21 s  ";
	reference "The International System of Units: 8th Edition 2006. Clause 4.1
	           P.J. Mohr and B.N. Taylor, Rev. Mod. Phys., 2005, 77, 1-107";
  }

  identity elementary-charge
  {
	description "It equals 1.602 176 53 (14) × 10−19 C";
	reference "The International System of Units: 8th Edition 2006. Clause 4.1
	           P.J. Mohr and B.N. Taylor, Rev. Mod. Phys., 2005, 77, 1-107";
  }

  identity bohr-radius
  {
	description "It equals 0.529 177 2108 (18) × 10−10 m ";
	reference "The International System of Units: 8th Edition 2006. Clause 4.1
	           P.J. Mohr and B.N. Taylor, Rev. Mod. Phys., 2005, 77, 1-107";
  }

  identity hartree-energy
  {
	description "It equals 4.359 744 17 (75) × 10−18 J ";
	reference "The International System of Units: 8th Edition 2006. Clause 4.1
	           P.J. Mohr and B.N. Taylor, Rev. Mod. Phys., 2005, 77, 1-107";
  }

  identity atomic-unit-of-time
  {
	description "It equals 2.418 884 326 505 (16) × 10−17 s";
	reference "The International System of Units: 8th Edition 2006. Clause 4.1
	           P.J. Mohr and B.N. Taylor, Rev. Mod. Phys., 2005, 77, 1-107";
  }

  //=============================================================================================
  //
  //                                      OTHER NON-SI UNITS
  //
  //=============================================================================================
  typedef kynematic-viscosity
  {
	type ieee1906-dot1-function:variable;
	units meter^2/second;             //  1 stokes (1 St) = 10-4 m2 s-1
	description "";
	reference "The International System of Units: 8th Edition 2006. Clause 4.1";
  }
}
